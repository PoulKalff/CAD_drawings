# Cinematic FreeCAD camera sequence for the ORIGINAL Nejsigvang model.
# Updated version with:
# - strong initial zoom-out and rise, so the camera avoids the house before the full orbit
# - full 360 exterior orbit at a large radius and high altitude to show the entire model
# - frontal entry through an exterior opening
# - straighter, more frontal passage through interior openings
# - frontal exit through an exterior opening
# - return to the exact start position
#
# Usage:
#   Open the original Nejsigvang_8(1).FCStd file and run this macro.

import math
import time
import FreeCAD
import FreeCADGui as Gui
from pivy import coin

FPS = 30
DURATION = 68.0
UP = coin.SbVec3f(0.0, 0.0, 1.0)

# Estimated house/model focus center from plan analysis
CENTER = FreeCAD.Vector(-4200.0, 22000.0, 1800.0)
ROOF_CENTER = FreeCAD.Vector(-4200.0, 22000.0, 2400.0)

# -----------------------------------------------------------------------------
# Route design notes
# -----------------------------------------------------------------------------
# 1) Start relatively near the southwest/front side.
# 2) Immediately pull back and upward while zooming out hard, to avoid contact and
#    reveal the full model from high above.
# 3) Make a full 360-degree exterior orbit at a large radius.
# 4) After the orbit, approach an exterior opening frontally along a straight line.
# 5) Move through interior openings mostly along straight axial segments.
# 6) Exit frontally through an exterior opening.
# 7) Return outside and finish exactly at the start point.
#
# All opening passages are kept as straight as practical with a frontal camera aim.

POS_PTS = [
    # ---- Start near front/southwest side ----
    FreeCAD.Vector(-13200.0, 14800.0, 3200.0),  # 0 exact start / exact end

    # ---- Strong pull-back + rise + zoom-out ----
    FreeCAD.Vector(-17000.0, 11800.0, 5200.0),
    FreeCAD.Vector(-20500.0,  9200.0, 7600.0),
    FreeCAD.Vector(-21500.0,  8500.0, 9800.0),  # 3 very wide establishing shot

    # ---- Full 360 orbit, staying wide and high ----
    FreeCAD.Vector(-12000.0,  7200.0, 9000.0),
    FreeCAD.Vector( -2500.0,  7000.0, 8600.0),
    FreeCAD.Vector(  7500.0, 10500.0, 8200.0),
    FreeCAD.Vector( 10200.0, 20000.0, 8000.0),
    FreeCAD.Vector(  7600.0, 29600.0, 8200.0),
    FreeCAD.Vector( -2500.0, 33800.0, 8600.0),
    FreeCAD.Vector(-12800.0, 33300.0, 9000.0),
    FreeCAD.Vector(-19600.0, 27200.0, 9200.0),
    FreeCAD.Vector(-21400.0, 18000.0, 9400.0),
    FreeCAD.Vector(-18800.0, 11000.0, 9200.0),

    # ---- Move back toward the south/front entry side, still clear of the house ----
    FreeCAD.Vector(-12800.0, 10400.0, 7600.0),
    FreeCAD.Vector( -9600.0, 11200.0, 5400.0),
    FreeCAD.Vector( -7000.0, 12000.0, 3600.0),
    FreeCAD.Vector( -5400.0, 12800.0, 2400.0),

    # ---- Straight frontal entry through south/front opening (movement mainly +Y) ----
    FreeCAD.Vector( -5000.0, 13800.0, 1900.0),
    FreeCAD.Vector( -5000.0, 15000.0, 1700.0),
    FreeCAD.Vector( -5000.0, 16200.0, 1650.0),  # through exterior opening

    # ---- Straight interior progression through openings (mainly +Y) ----
    FreeCAD.Vector( -5000.0, 18200.0, 1650.0),
    FreeCAD.Vector( -5000.0, 20200.0, 1650.0),
    FreeCAD.Vector( -5000.0, 22200.0, 1650.0),

    # ---- Turn and pass frontally through interior openings (mainly +X) ----
    FreeCAD.Vector( -3400.0, 22200.0, 1650.0),
    FreeCAD.Vector( -1800.0, 22200.0, 1650.0),
    FreeCAD.Vector(  -200.0, 22200.0, 1670.0),
    FreeCAD.Vector(  1400.0, 22200.0, 1700.0),

    # ---- Final line-up and frontal exit through east opening (movement mainly +X) ----
    FreeCAD.Vector(  2800.0, 21400.0, 1750.0),
    FreeCAD.Vector(  3900.0, 20400.0, 1850.0),
    FreeCAD.Vector(  5000.0, 19400.0, 2100.0),  # through exterior opening
    FreeCAD.Vector(  6600.0, 18200.0, 2800.0),

    # ---- Return outside in a broad sweep back to exact start ----
    FreeCAD.Vector(  6200.0, 13800.0, 4200.0),
    FreeCAD.Vector(  2600.0, 10800.0, 4800.0),
    FreeCAD.Vector( -2600.0,  9500.0, 5100.0),
    FreeCAD.Vector( -7600.0, 10800.0, 5000.0),
    FreeCAD.Vector(-11000.0, 12800.0, 4300.0),
    FreeCAD.Vector(-13200.0, 14800.0, 3200.0),  # exact end = exact start
]

# Corresponding look targets.
# Exterior = house-focused. Opening passages = frontal / look straight through the opening.
TGT_PTS = [
    CENTER,
    CENTER,
    CENTER,
    ROOF_CENTER,

    ROOF_CENTER,
    ROOF_CENTER,
    ROOF_CENTER,
    ROOF_CENTER,
    ROOF_CENTER,
    ROOF_CENTER,
    ROOF_CENTER,
    ROOF_CENTER,
    ROOF_CENTER,
    ROOF_CENTER,

    CENTER,
    CENTER,
    FreeCAD.Vector(-5000.0, 15000.0, 1800.0),
    FreeCAD.Vector(-5000.0, 16500.0, 1700.0),

    # frontal entry targets: always look straight forward along +Y
    FreeCAD.Vector(-5000.0, 15600.0, 1700.0),
    FreeCAD.Vector(-5000.0, 17000.0, 1660.0),
    FreeCAD.Vector(-5000.0, 18600.0, 1650.0),

    # interior openings along +Y
    FreeCAD.Vector(-5000.0, 19800.0, 1650.0),
    FreeCAD.Vector(-5000.0, 21800.0, 1650.0),
    FreeCAD.Vector(-5000.0, 23000.0, 1650.0),

    # interior openings along +X
    FreeCAD.Vector(-2600.0, 22200.0, 1650.0),
    FreeCAD.Vector(-1000.0, 22200.0, 1650.0),
    FreeCAD.Vector(  600.0, 22200.0, 1670.0),
    FreeCAD.Vector( 2200.0, 22200.0, 1700.0),

    # frontal exit targets
    FreeCAD.Vector( 4200.0, 20400.0, 1850.0),
    FreeCAD.Vector( 5200.0, 19400.0, 2100.0),
    FreeCAD.Vector( 6400.0, 18200.0, 2600.0),
    CENTER,

    CENTER,
    CENTER,
    CENTER,
    CENTER,
    CENTER,
    CENTER,
]

# Field-of-view in degrees at the control points.
# Larger number = stronger zoom out / wider view.
FOV_PTS = [
    44.0,   # start, slightly tighter
    56.0,
    68.0,
    82.0,   # strong zoom-out establishing shot

    80.0,
    78.0,
    76.0,
    74.0,
    74.0,
    76.0,
    78.0,
    80.0,
    82.0,
    80.0,

    72.0,
    62.0,
    54.0,
    46.0,

    42.0,
    38.0,
    36.0,

    34.0,
    34.0,
    34.0,

    34.0,
    34.0,
    36.0,
    38.0,

    42.0,
    48.0,
    56.0,
    62.0,

    66.0,
    62.0,
    56.0,
    50.0,
    46.0,
    44.0,
]

if FreeCAD.ActiveDocument is None:
    raise RuntimeError("Open the original Nejsigvang FCStd file before running this macro.")

Gui.runCommand("Std_PerspectiveCamera", 1)
view = Gui.ActiveDocument.ActiveView
cam = view.getCameraNode()


def cumulative_lengths(points):
    vals = [0.0]
    for i in range(1, len(points)):
        vals.append(vals[-1] + (points[i] - points[i - 1]).Length)
    return vals


def sample_piecewise_vectors(points, cumlen, u):
    u = max(0.0, min(1.0, u))
    total = cumlen[-1]
    if total <= 0.0:
        return points[0]
    d = u * total
    for i in range(len(cumlen) - 1):
        a = cumlen[i]
        b = cumlen[i + 1]
        if d <= b or i == len(cumlen) - 2:
            seg = max(1e-9, b - a)
            t = (d - a) / seg
            return points[i] * (1.0 - t) + points[i + 1] * t
    return points[-1]


def sample_piecewise_scalars(values, cumlen, u):
    u = max(0.0, min(1.0, u))
    total = cumlen[-1]
    if total <= 0.0:
        return values[0]
    d = u * total
    for i in range(len(cumlen) - 1):
        a = cumlen[i]
        b = cumlen[i + 1]
        if d <= b or i == len(cumlen) - 2:
            seg = max(1e-9, b - a)
            t = (d - a) / seg
            return values[i] * (1.0 - t) + values[i + 1] * t
    return values[-1]


path_lengths = cumulative_lengths(POS_PTS)
# For target and FOV we use the same point progression count as the route.
# This keeps aiming and zoom transitions aligned with the route sections.
frames = max(2, int(FPS * DURATION))
dt = 1.0 / FPS

for frame in range(frames):
    u0 = frame / float(frames - 1)
    # globally eased timing for gentler cinematic acceleration/deceleration
    u = u0*u0*(3.0 - 2.0*u0)

    pos = sample_piecewise_vectors(POS_PTS, path_lengths, u)
    target = sample_piecewise_vectors(TGT_PTS, path_lengths, u)
    fov_deg = sample_piecewise_scalars(FOV_PTS, path_lengths, u)
    fov_deg = max(28.0, min(95.0, fov_deg))

    if (target - pos).Length < 1.0:
        target = target + FreeCAD.Vector(0.0, 1.0, 0.0)

    cam.position.setValue(float(pos.x), float(pos.y), float(pos.z))
    try:
        cam.heightAngle.setValue(math.radians(fov_deg))
    except Exception:
        pass
    cam.pointAt(coin.SbVec3f(float(target.x), float(target.y), float(target.z)), UP)

    Gui.updateGui()
    time.sleep(dt)

FreeCAD.Console.PrintMessage(
    "Cinematic high/wide 360 with frontal openings finished.\n"
)
